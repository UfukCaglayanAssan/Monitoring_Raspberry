TESCOM-BMS-MIB DEFINITIONS ::= BEGIN

IMPORTS
    MODULE-IDENTITY, OBJECT-TYPE, NOTIFICATION-TYPE,
    Integer32, Counter32, Gauge32, enterprises
        FROM SNMPv2-SMI
    DisplayString, TimeStamp, TEXTUAL-CONVENTION
        FROM SNMPv2-TC
    MODULE-COMPLIANCE, OBJECT-GROUP, NOTIFICATION-GROUP
        FROM SNMPv2-CONF;

--
-- Module Identity
--
tescomBmsMIB MODULE-IDENTITY
    LAST-UPDATED "202410280000Z"
    ORGANIZATION "TESCOM A.S."
    CONTACT-INFO
        "TESCOM A.S.
         E-mail: support@tescom.com.tr"
    DESCRIPTION
        "TESCOM Battery Management System MIB
         Bu MIB, batarya yonetim sistemi icin SNMP erisim saglar.
         Kol ve batarya bilgileri, alarmlar ve status verileri icerir."
    REVISION "202410280000Z"
    DESCRIPTION
        "Ilk versiyon - Batarya yonetim sistemi icin SNMP MIB tanimlari"
    ::= { enterprises 1001 }

--
-- Textual Conventions (bacs2.mib'den alındı)
--
PositiveInteger ::= TEXTUAL-CONVENTION
    DISPLAY-HINT "d"
    STATUS       current
    DESCRIPTION
        "This data type is a non-zero and non-negative value."
    SYNTAX       INTEGER (1..2147483647)

NonNegativeInteger ::= TEXTUAL-CONVENTION
    DISPLAY-HINT "d"
    STATUS       current
    DESCRIPTION
        "This data type is a non-negative value."
    SYNTAX       INTEGER (0..2147483647)

--
-- Ana Gruplar
--
tescomBmsSystem     OBJECT IDENTIFIER ::= { tescomBmsMIB 1 }
tescomBmsArms       OBJECT IDENTIFIER ::= { tescomBmsMIB 2 }
tescomBmsBatteries  OBJECT IDENTIFIER ::= { tescomBmsMIB 3 }
tescomBmsAlarms     OBJECT IDENTIFIER ::= { tescomBmsMIB 4 }
tescomBmsTraps      OBJECT IDENTIFIER ::= { tescomBmsMIB 5 }

-- ============================================
-- Sistem Bilgileri (1.3.6.1.4.1.1001.1.x)
-- ============================================

systemInfo OBJECT-TYPE
    SYNTAX      DisplayString (SIZE (0..255))
    MAX-ACCESS  read-only
    STATUS      current
    DESCRIPTION
        "Sistem bilgisi - Python versiyonu ve platform"
    ::= { tescomBmsSystem 1 }

totalBatteryCount OBJECT-TYPE
    SYNTAX      NonNegativeInteger
    UNITS       "batteries"
    MAX-ACCESS  read-only
    STATUS      current
    DESCRIPTION
        "Sistemdeki toplam batarya sayisi"
    ::= { tescomBmsSystem 2 }

totalArmCount OBJECT-TYPE
    SYNTAX      NonNegativeInteger
    UNITS       "arms"
    MAX-ACCESS  read-only
    STATUS      current
    DESCRIPTION
        "Sistemdeki toplam aktif kol sayisi"
    ::= { tescomBmsSystem 3 }

systemStatus OBJECT-TYPE
    SYNTAX      INTEGER {
        stopped(0),
        running(1),
        error(2)
    }
    MAX-ACCESS  read-only
    STATUS      current
    DESCRIPTION
        "Sistem durumu: 0=Durdurulmus, 1=Calisiyor, 2=Hata"
    ::= { tescomBmsSystem 4 }

lastUpdateTime OBJECT-TYPE
    SYNTAX      DisplayString (SIZE (0..32))
    MAX-ACCESS  read-only
    STATUS      current
    DESCRIPTION
        "Son guncelleme zamani (YYYY-MM-DD HH:MM:SS formatinda)"
    ::= { tescomBmsSystem 5 }

dataCount OBJECT-TYPE
    SYNTAX      NonNegativeInteger
    MAX-ACCESS  read-only
    STATUS      current
    DESCRIPTION
        "RAM'de saklanan toplam veri sayısı"
    ::= { tescomBmsSystem 6 }

-- ============================================
-- KOL TABLOSU (bacs2.mib bacsModuleTable benzeri)
-- (1.3.6.1.4.1.1001.2.x)
-- ============================================

ArmEntry ::= SEQUENCE {
    armIndex            PositiveInteger,
    armSlaveCount       NonNegativeInteger,
    armCurrent          Integer32,
    armHumidity         NonNegativeInteger,
    armNtc1Temp         Integer32,
    armNtc2Temp         Integer32,
    armStatus           INTEGER,
    armAlarmFlags       NonNegativeInteger
}

armTable OBJECT-TYPE
    SYNTAX      SEQUENCE OF ArmEntry
    MAX-ACCESS  not-accessible
    STATUS      current
    DESCRIPTION
        "Kol bilgileri tablosu. Her kol için bir entry içerir."
    ::= { tescomBmsArms 1 }

armEntry OBJECT-TYPE
    SYNTAX      ArmEntry
    MAX-ACCESS  not-accessible
    STATUS      current
    DESCRIPTION
        "Bir kola ait bilgileri içeren entry."
    INDEX       { armIndex }
    ::= { armTable 1 }

armIndex OBJECT-TYPE
    SYNTAX      PositiveInteger (1..4)
    MAX-ACCESS  not-accessible
    STATUS      current
    DESCRIPTION
        "Kol numarası (1-4 arası)"
    ::= { armEntry 1 }

armSlaveCount OBJECT-TYPE
    SYNTAX      NonNegativeInteger
    UNITS       "batteries"
    MAX-ACCESS  read-only
    STATUS      current
    DESCRIPTION
        "Bu koldaki batarya sayisi"
    ::= { armEntry 2 }

armCurrent OBJECT-TYPE
    SYNTAX      Integer32
    UNITS       "0.1 Ampere"
    MAX-ACCESS  read-only
    STATUS      current
    DESCRIPTION
        "Kol akım değeri (Ampere * 10)"
    ::= { armEntry 3 }

armHumidity OBJECT-TYPE
    SYNTAX      NonNegativeInteger
    UNITS       "0.1 %"
    MAX-ACCESS  read-only
    STATUS      current
    DESCRIPTION
        "Kol nem değeri (% * 10)"
    ::= { armEntry 4 }

armNtc1Temp OBJECT-TYPE
    SYNTAX      Integer32
    UNITS       "0.1 Celsius"
    MAX-ACCESS  read-only
    STATUS      current
    DESCRIPTION
        "Kol NTC1 sicaklik degeri (C * 10)"
    ::= { armEntry 5 }

armNtc2Temp OBJECT-TYPE
    SYNTAX      Integer32
    UNITS       "0.1 Celsius"
    MAX-ACCESS  read-only
    STATUS      current
    DESCRIPTION
        "Kol NTC2 sicaklik degeri (C * 10)"
    ::= { armEntry 6 }

armStatus OBJECT-TYPE
    SYNTAX      INTEGER {
        normal(0),
        alarm(1)
    }
    MAX-ACCESS  read-only
    STATUS      current
    DESCRIPTION
        "Kol genel durumu: 0=Normal, 1=Alarm var"
    ::= { armEntry 7 }

armAlarmFlags OBJECT-TYPE
    SYNTAX      NonNegativeInteger
    UNITS       "HEX flags"
    MAX-ACCESS  read-only
    STATUS      current
    DESCRIPTION
        "Kol alarm bayraklari (HEX formatinda):
         0x0=Alarm yok
         0x1=Yuksek Akim
         0x2=Yuksek Nem
         0x4=Yuksek Ortam Sicakligi
         0x8=Yuksek Kol Sicakligi"
    ::= { armEntry 8 }

-- ============================================
-- BATARYA TABLOSU (bacs2.mib bacsModuleTable benzeri)
-- (1.3.6.1.4.1.1001.3.x)
-- ============================================

BatteryEntry ::= SEQUENCE {
    batteryArmIndex         PositiveInteger,
    batteryIndex            PositiveInteger,
    batteryVoltage          NonNegativeInteger,
    batterySoc              NonNegativeInteger,
    batteryRimt             Integer32,
    batterySoh              NonNegativeInteger,
    batteryNtc1             Integer32,
    batteryNtc2             Integer32,
    batteryNtc3             Integer32,
    batteryStatus           INTEGER,
    batteryAlarmFlags       NonNegativeInteger
}

batteryTable OBJECT-TYPE
    SYNTAX      SEQUENCE OF BatteryEntry
    MAX-ACCESS  not-accessible
    STATUS      current
    DESCRIPTION
        "Batarya bilgileri tablosu. Her batarya için bir entry içerir."
    ::= { tescomBmsBatteries 1 }

batteryEntry OBJECT-TYPE
    SYNTAX      BatteryEntry
    MAX-ACCESS  not-accessible
    STATUS      current
    DESCRIPTION
        "Bir bataryaya ait bilgileri içeren entry."
    INDEX       { batteryArmIndex, batteryIndex }
    ::= { batteryTable 1 }

batteryArmIndex OBJECT-TYPE
    SYNTAX      PositiveInteger (1..4)
    MAX-ACCESS  not-accessible
    STATUS      current
    DESCRIPTION
        "Bataryanın bağlı olduğu kol numarası (1-4)"
    ::= { batteryEntry 1 }

batteryIndex OBJECT-TYPE
    SYNTAX      PositiveInteger (1..120)
    MAX-ACCESS  not-accessible
    STATUS      current
    DESCRIPTION
        "Batarya adresi (1-120 arası)"
    ::= { batteryEntry 2 }

batteryVoltage OBJECT-TYPE
    SYNTAX      NonNegativeInteger
    UNITS       "mV"
    MAX-ACCESS  read-only
    STATUS      current
    DESCRIPTION
        "Batarya gerilim degeri (miliVolt cinsinden)"
    ::= { batteryEntry 3 }

batterySoc OBJECT-TYPE
    SYNTAX      NonNegativeInteger (0..100)
    UNITS       "%"
    MAX-ACCESS  read-only
    STATUS      current
    DESCRIPTION
        "Batarya sarj durumu (State of Charge, %)"
    ::= { batteryEntry 4 }

batteryRimt OBJECT-TYPE
    SYNTAX      Integer32
    UNITS       "0.1 Celsius"
    MAX-ACCESS  read-only
    STATUS      current
    DESCRIPTION
        "Batarya modul sicakligi (C * 10)"
    ::= { batteryEntry 5 }

batterySoh OBJECT-TYPE
    SYNTAX      NonNegativeInteger (0..100)
    UNITS       "%"
    MAX-ACCESS  read-only
    STATUS      current
    DESCRIPTION
        "Batarya saglik durumu (State of Health, %)"
    ::= { batteryEntry 6 }

batteryNtc1 OBJECT-TYPE
    SYNTAX      Integer32
    UNITS       "0.1 Celsius"
    MAX-ACCESS  read-only
    STATUS      current
    DESCRIPTION
        "Batarya NTC1 sicaklik sensoru (C * 10)"
    ::= { batteryEntry 7 }

batteryNtc2 OBJECT-TYPE
    SYNTAX      Integer32
    UNITS       "0.1 Celsius"
    MAX-ACCESS  read-only
    STATUS      current
    DESCRIPTION
        "Batarya NTC2 sicaklik sensoru (C * 10)"
    ::= { batteryEntry 8 }

batteryNtc3 OBJECT-TYPE
    SYNTAX      Integer32
    UNITS       "0.1 Celsius"
    MAX-ACCESS  read-only
    STATUS      current
    DESCRIPTION
        "Batarya NTC3 sicaklik sensoru (C * 10)"
    ::= { batteryEntry 9 }

batteryStatus OBJECT-TYPE
    SYNTAX      INTEGER {
        normal(0),
        alarm(1)
    }
    MAX-ACCESS  read-only
    STATUS      current
    DESCRIPTION
        "Batarya genel durumu: 0=Normal, 1=Alarm var"
    ::= { batteryEntry 10 }

batteryAlarmFlags OBJECT-TYPE
    SYNTAX      NonNegativeInteger
    UNITS       "HEX flags"
    MAX-ACCESS  read-only
    STATUS      current
    DESCRIPTION
        "Batarya alarm bayraklari (HEX formatinda):
         0x0=Alarm yok
         0x1=Dusuk Gerilim Uyarisi
         0x2=Dusuk Gerilim Alarmi
         0x4=Yuksek Gerilim Uyarisi
         0x8=Yuksek Gerilim Alarmi
         0x10=Modul Sicaklik Alarmi
         0x20=Pozitif Kutup Sicaklik Alarmi
         0x40=Negatif Kutup Sicaklik Alarmi"
    ::= { batteryEntry 11 }

-- ============================================
-- ALARM BİLGİLERİ (bacs2.mib bacsAlarms benzeri)
-- (1.3.6.1.4.1.1001.4.x)
-- ============================================

tescomAlarmsPresent OBJECT-TYPE
    SYNTAX      Gauge32
    MAX-ACCESS  read-only
    STATUS      current
    DESCRIPTION
        "Sistemdeki toplam aktif alarm sayısı"
    ::= { tescomBmsAlarms 1 }

tescomArmAlarmsPresent OBJECT-TYPE
    SYNTAX      Gauge32
    MAX-ACCESS  read-only
    STATUS      current
    DESCRIPTION
        "Kol alarmlarinin sayisi"
    ::= { tescomBmsAlarms 2 }

tescomBatteryAlarmsPresent OBJECT-TYPE
    SYNTAX      Gauge32
    MAX-ACCESS  read-only
    STATUS      current
    DESCRIPTION
        "Batarya alarmlarinin sayisi"
    ::= { tescomBmsAlarms 3 }

-- Alarm Tablosu (bacs2.mib bacsAlarmTable benzeri)
AlarmEntry ::= SEQUENCE {
    alarmId             PositiveInteger,
    alarmArmIndex       NonNegativeInteger,
    alarmBatteryIndex   NonNegativeInteger,
    alarmType           INTEGER,
    alarmDescription    DisplayString,
    alarmTime           TimeStamp,
    alarmStatus         INTEGER
}

alarmTable OBJECT-TYPE
    SYNTAX      SEQUENCE OF AlarmEntry
    MAX-ACCESS  not-accessible
    STATUS      current
    DESCRIPTION
        "Aktif alarm listesi tablosu"
    ::= { tescomBmsAlarms 4 }

alarmEntry OBJECT-TYPE
    SYNTAX      AlarmEntry
    MAX-ACCESS  not-accessible
    STATUS      current
    DESCRIPTION
        "Bir alarm kaydı"
    INDEX       { alarmId }
    ::= { alarmTable 1 }

alarmId OBJECT-TYPE
    SYNTAX      PositiveInteger
    MAX-ACCESS  read-only
    STATUS      current
    DESCRIPTION
        "Alarm benzersiz ID'si"
    ::= { alarmEntry 1 }

alarmArmIndex OBJECT-TYPE
    SYNTAX      NonNegativeInteger (0..4)
    MAX-ACCESS  read-only
    STATUS      current
    DESCRIPTION
        "Alarmin ilgili oldugu kol numarasi (0=Sistem geneli, 1-4=Kol)"
    ::= { alarmEntry 2 }

alarmBatteryIndex OBJECT-TYPE
    SYNTAX      NonNegativeInteger (0..120)
    MAX-ACCESS  read-only
    STATUS      current
    DESCRIPTION
        "Alarmin ilgili oldugu batarya adresi (0=Kol alarmi, 1-120=Batarya)"
    ::= { alarmEntry 3 }

alarmType OBJECT-TYPE
    SYNTAX      INTEGER {
        armHighCurrent(1),
        armHighHumidity(2),
        armHighAmbientTemp(3),
        armHighTemp(4),
        batteryLowVoltageWarn(11),
        batteryLowVoltageAlarm(12),
        batteryHighVoltageWarn(13),
        batteryHighVoltageAlarm(14),
        batteryModuleTemp(15),
        batteryPositivePoleTemp(16),
        batteryNegativePoleTemp(17)
    }
    MAX-ACCESS  read-only
    STATUS      current
    DESCRIPTION
        "Alarm tipi"
    ::= { alarmEntry 4 }

alarmDescription OBJECT-TYPE
    SYNTAX      DisplayString (SIZE (0..255))
    MAX-ACCESS  read-only
    STATUS      current
    DESCRIPTION
        "Alarm aciklamasi (ASCII formatinda)"
    ::= { alarmEntry 5 }

alarmTime OBJECT-TYPE
    SYNTAX      TimeStamp
    MAX-ACCESS  read-only
    STATUS      current
    DESCRIPTION
        "Alarmin olusma zamani (sysUpTime)"
    ::= { alarmEntry 6 }

alarmStatus OBJECT-TYPE
    SYNTAX      INTEGER {
        active(1),
        resolved(2)
    }
    MAX-ACCESS  read-only
    STATUS      current
    DESCRIPTION
        "Alarm durumu: 1=Aktif, 2=Cozuldu"
    ::= { alarmEntry 7 }

-- ============================================
-- SNMP Trap Tanımları (bacs2.mib bacsTrapAlarmEntryAdded benzeri)
-- ============================================

tescomAlarmTrap NOTIFICATION-TYPE
    OBJECTS     { alarmId, alarmArmIndex, alarmBatteryIndex, alarmType, alarmDescription }
    STATUS      current
    DESCRIPTION
        "Yeni bir alarm olustugunda gonderilen trap"
    ::= { tescomBmsTraps 1 }

tescomAlarmClearedTrap NOTIFICATION-TYPE
    OBJECTS     { alarmId, alarmArmIndex, alarmBatteryIndex, alarmType, alarmDescription }
    STATUS      current
    DESCRIPTION
        "Bir alarm cozuldugunde gonderilen trap"
    ::= { tescomBmsTraps 2 }

tescomSystemStartTrap NOTIFICATION-TYPE
    OBJECTS     { systemInfo }
    STATUS      current
    DESCRIPTION
        "Sistem baslatildiginda gonderilen trap"
    ::= { tescomBmsTraps 3 }

END
